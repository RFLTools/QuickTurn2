;
;
;     Program written by Robert Livingston, 2015
;
;     QTMAKETEMPBLOCK creates a temporary block copied from the supplied entity using only its LINES ARCS CIRCLES POLYLINES and NESTED BLOCKS
;
;
(defun QT:MAKETEMPBLOCK (ENT / BLOCKANG BLOCKLAYER BLOCKNAME BLOCKP ENT2 ENTB ENTLIST ENTLISTB ENTLISTNODE ENTLISTNEW ENTNEW NODE SX SY SZ TMP)
 (setq ENTLIST (entget ENT))
 (if (/= "INSERT" (cdr (assoc 0 ENTLIST)))
  (eval nil)
  (progn
   (setq BLOCKNAME (cdr (assoc 2 ENTLIST)))
   (setq BLOCKLAYER (cdr (assoc 8 ENTLIST)))
   (setq BLOCKP (cdr (assoc 10 ENTLIST)))
   (setq SX (cdr (assoc 41 ENTLIST)))
   (setq SY (cdr (assoc 42 ENTLIST)))
   (setq SZ (cdr (assoc 43 ENTLIST)))
   (setq BLOCKANG (cdr (assoc 50 ENTLIST)))
   (setq ENTLIST (tblsearch "BLOCK" BLOCKNAME))
   (setq ENT2 (cdr (assoc -2 ENTLIST)))
   (setq ENTLIST (entget ENT2))
   (setq ENTLISTNEW (list (list (cons 0 "BLOCK")
                                (cons 2 "*U")
                                (assoc 8 ENTLIST)
                                (cons 70 1)
                                (list 10 0.0 0.0 0.0)
                          )
                    )
   )
   (while (/= nil ENT2)
    (setq ENTLIST (entget ENT2))
    (setq ENTLISTNODE nil)
    (if (and (/= "DEFPOINTS" (strcase (cdr (assoc 8 ENTLIST))))
             (/= "ATTDEF" (cdr (assoc 0 ENTLIST)))
        )
     (cond ((= "ARC" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 40 (car NODE))
                     (= 48 (car NODE))
                     (= 50 (car NODE))
                     (= 51 (car NODE))
                     (= 62 (car NODE))
                     (= 100 (car NODE))
                     (= 210 (car NODE))
                     (= 220 (car NODE))
                     (= 230 (car NODE))
                 )
              (setq ENTLISTNODE (append ENTLISTNODE (list NODE)))
             )
            )
           )
           ((= "INSERT" (cdr (assoc 0 ENTLIST)))
            (progn
             (if (setq ENTB (QT:MAKETEMPBLOCK (cdr (assoc -1 ENTLIST))))
              (progn
               (setq ENTLISTB (entget ENTB))
               (foreach NODE ENTLISTB
                (if (or (= 0 (car NODE))
                        (= 2 (car NODE))
                        (= 6 (car NODE))
                        (= 8 (car NODE))
                        (= 10 (car NODE))
                        (= 20 (car NODE))
                        (= 30 (car NODE))
                        (= 40 (car NODE))
                        (= 41 (car NODE))
                        (= 42 (car NODE))
                        (= 43 (car NODE))
                        (= 44 (car NODE))
                        (= 45 (car NODE))
                        (= 48 (car NODE))
                        (= 50 (car NODE))
                        (= 62 (car NODE))
                        (= 70 (car NODE))
                        (= 71 (car NODE))
                        (= 100 (car NODE))
                        (= 210 (car NODE))
                        (= 220 (car NODE))
                        (= 230 (car NODE))
                    )
                 (setq ENTLISTNODE (append ENTLISTNODE (list NODE)))
                )
               )
               (entdel ENTB)
              )
             )
            )
           )
           ((= "CIRCLE" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 40 (car NODE))
                     (= 48 (car NODE))
                     (= 62 (car NODE))
                     (= 100 (car NODE))
                     (= 210 (car NODE))
                     (= 220 (car NODE))
                     (= 230 (car NODE))
                 )
              (setq ENTLISTNODE (append ENTLISTNODE (list NODE)))
             )
            )
           )
           ((= "LINE" (cdr (assoc 0 ENTLIST)))
            (foreach NODE ENTLIST
             (if (or (= 0 (car NODE))
                     (= 6 (car NODE))
                     (= 8 (car NODE))
                     (= 10 (car NODE))
                     (= 11 (car NODE))
                     (= 20 (car NODE))
                     (= 21 (car NODE))
                     (= 30 (car NODE))
                     (= 31 (car NODE))
                     (= 48 (car NODE))
                     (= 62 (car NODE))
                     (= 100 (car NODE))
                     (= 210 (car NODE))
                     (= 220 (car NODE))
                     (= 230 (car NODE))
                 )
              (setq ENTLISTNODE (append ENTLISTNODE (list NODE)))
             )
            )
           )
           ((= "LWPOLYLINE" (cdr (assoc 0 ENTLIST)))
            (foreach NODE ENTLIST
             (if (or (= 0 (car NODE))
                     (= 6 (car NODE))
                     (= 8 (car NODE))
                     (= 10 (car NODE))
                     (= 20 (car NODE))
                     (= 38 (car NODE))
                     (= 39 (car NODE))
                     (= 40 (car NODE))
                     (= 41 (car NODE))
                     (= 42 (car NODE))
                     (= 43 (car NODE))
                     (= 48 (car NODE))
                     (= 62 (car NODE))
                     (= 70 (car NODE))
                     (= 90 (car NODE))
                     (= 100 (car NODE))
                     (= 210 (car NODE))
                     (= 220 (car NODE))
                     (= 230 (car NODE))
                 )
              (setq ENTLISTNODE (append ENTLISTNODE (list NODE)))
             )
            )
           )
           ((= "POLYLINE" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 40 (car NODE))
                     (= 41 (car NODE))
                     (= 48 (car NODE))
                     (= 62 (car NODE))
                     (= 70 (car NODE))
                     (= 71 (car NODE))
                     (= 72 (car NODE))
                     (= 73 (car NODE))
                     (= 74 (car NODE))
                     (= 75 (car NODE))
                     (= 100 (car NODE))
                     (= 210 (car NODE))
                     (= 220 (car NODE))
                     (= 230 (car NODE))
                 )
              (setq ENTLISTNODE (append ENTLISTNODE (list NODE)))
             )
            )
           )
           ((= "VERTEX" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 40 (car NODE))
                     (= 41 (car NODE))
                     (= 42 (car NODE))
                     (= 48 (car NODE))
                     (= 50 (car NODE))
                     (= 62 (car NODE))
                     (= 70 (car NODE))
                     (= 71 (car NODE))
                     (= 72 (car NODE))
                     (= 73 (car NODE))
                     (= 74 (car NODE))
                     (= 100 (car NODE))
                 )
              (setq ENTLISTNODE (append ENTLISTNODE (list NODE)))
             )
            )
           )
           ((= "SEQEND" (cdr (assoc 0 ENTLIST)))
            (foreach NODE ENTLIST
             (if (or (= 0 (car NODE))
                 )
              (setq ENTLISTNODE (append ENTLISTNODE (list NODE)))
             )
            )
           )
           ((= "POINT" (cdr (assoc 0 ENTLIST)))
            (foreach NODE ENTLIST
             (if (or (= 0 (car NODE))
                     (= 6 (car NODE))
                     (= 8 (car NODE))
                     (= 10 (car NODE))
                     (= 20 (car NODE))
                     (= 30 (car NODE))
                     (= 39 (car NODE))
                     (= 48 (car NODE))
                     (= 50 (car NODE))
                     (= 62 (car NODE))
                     (= 100 (car NODE))
                     (= 220 (car NODE))
                     (= 230 (car NODE))
                 )
              (setq ENTLISTNODE (append ENTLISTNODE (list NODE)))
             )
            )
           )
     )
    )
    (if (/= nil ENTLISTNODE) (setq ENTLISTNEW (append ENTLISTNEW (list ENTLISTNODE))))
    (setq ENT2 (entnext ENT2))
   )
   (setq ENTLISTNEW (append ENTLISTNEW (list (list (cons 0 "ENDBLK")))))
   (entmake)
   (foreach NODE ENTLISTNEW
    (setq TMP (entmake NODE))
   )
   (if (= nil TMP)
    (eval nil)
    (progn
     (entmake (list (cons 0 "INSERT")
                    (cons 2 TMP)
                    (cons 8 BLOCKLAYER)
                    (cons 10 BLOCKP)
                    (cons 41 SX)
                    (cons 42 SY)
                    (cons 43 SZ)
                    (cons 50 BLOCKANG)
              )
     )
     (entlast)
    )
   )
  )
 )
)

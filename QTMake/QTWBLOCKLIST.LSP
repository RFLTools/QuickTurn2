;
;
;     Program written by Robert Livingston, 2015-04-14
;
;     QTWBLOCKLIST writes lisp code to create a selected set of blocks
;
;
(defun C:QTWBLOCKLIST (/ *error* BLOCKNAME BLOCKNESTLIST C CMDECHO CODE DIMZIN ENT ENTLIST ENTSET LSTSEARCH NODE OUTFILE VAL)
 (setq CMDECHO (getvar "CMDECHO"))
 (setvar "CMDECHO" 0)
 (setq DIMZIN (getvar "DIMZIN"))
 (setvar "DIMZIN" 8)

 (defun *error* (msg)
  (if (/= nil OUTFILE) (close OUTFILE))
  (setvar "CMDECHO" CMDECHO)
  (setvar "DIMZIN" DIMZIN)
  ;(setq *error* nil)
  (princ msg)
 )

 (defun LSTSEARCH (STR LST / NODE RES)
  (setq RES nil)
  (foreach NODE LST
   (if (= (strcase NODE) (strcase STR)) (setq RES T))
  )
  RES
 )
 
 (princ "\nSelect vehicle blocks : ")
 (if (/= nil (setq ENTSET (ssget)))
  (if (/= nil (setq OUTFILE (getfiled "Select a block file" "" "" 1)))
   (progn
    (setq BLOCKNESTLIST nil)
    (setq OUTFILE (open OUTFILE "w"))
    (princ "(defun QT:MAKE (BLKNAME / )\n" OUTFILE)
    (princ " (cond\n" OUTFILE)
    (setq C 0)
    (while (< C (sslength ENTSET))
     (setq ENT (ssname ENTSET C))
     (if (= "INSERT" (cdr (assoc 0 (setq ENTLIST (entget ENT)))))
      (progn
       (princ (strcat "       ((= (strcase BLKNAME) (strcase \"" (cdr (assoc 2 ENTLIST)) "\"))\n") OUTFILE)
       (princ "        (progn\n" OUTFILE)
       (princ "         (entmake)\n" OUTFILE)
       (princ "         (entmake\n" OUTFILE)
       (princ "          (list\n" OUTFILE)
       (setq ENTLIST (tblsearch "BLOCK" (cdr (assoc 2 ENTLIST))))
       (setq ENT (cdr (assoc -2 ENTLIST)))
       (while (/= nil ENTLIST)
        (setq NODE (car ENTLIST))
        (setq ENTLIST (cdr ENTLIST))
        (setq CODE (car NODE))
        (if (and (>= CODE 0) (<= CODE 100) (/= CODE 5))
         (if (= (vl-list-length NODE) nil)
          (progn
           (princ
            (strcat "           (cons "
                    (itoa CODE)
                    " "
                    (if (numberp (cdr NODE))
                     (rtos (cdr NODE) 2 8)
                     (strcat "\"" (cdr NODE) "\"")
                    )
                    ")\n"
            )
            OUTFILE
           )
          )
          (progn
           (princ "           (list" OUTFILE)
           (foreach VAL NODE (princ " " OUTFILE)
                             (if (numberp VAL)
                                 (princ (rtos VAL 2 8) OUTFILE)
                                 (princ (strcat "\"" VAL "\"") OUTFILE)
                             )
           )
           (princ ")\n" OUTFILE)
          )
         )
        )
       )
       (princ "          )\n" OUTFILE)
       (princ "         )\n" OUTFILE)
       (while (/= ENT nil)
        (setq ENTLIST (entget ENT))
        (if (= "INSERT" (cdr (assoc 0 ENTLIST)))
         (if (= nil (LSTSEARCH (cdr (assoc 2 ENTLIST)) BLOCKNESTLIST))
          (setq BLOCKNESTLIST (append BLOCKNESTLIST (list (cdr (assoc 2 ENTLIST)))))
         )
        )
        (setq ENT (entnext ENT))
        (princ "         (entmake\n" OUTFILE)
        (princ "          (list\n" OUTFILE)
        (while (/= ENTLIST nil)
         (setq NODE (car ENTLIST))
         (setq ENTLIST (cdr ENTLIST))
         (setq CODE (car NODE))
         (if (and (>= CODE 0) (<= CODE 100) (/= CODE 5))
          (if (= (vl-list-length NODE) nil)
           (progn
            (princ
             (strcat "           (cons "
                     (itoa CODE)
                     " "
                     (if (numberp (cdr NODE))
                      (rtos (cdr NODE) 2 8)
                      (strcat "\"" (cdr NODE) "\"")
                     )
                     ")\n"
             )
             OUTFILE
            )
           )
           (progn
            (princ "           (list" OUTFILE)
            (foreach VAL NODE (princ " " OUTFILE)
                              (if (numberp VAL)
                                  (princ (rtos VAL 2 8) OUTFILE)
                                  (princ (strcat "\"" VAL "\"") OUTFILE)
                              )
            )
            (princ ")\n" OUTFILE)
           )
          )
         )
        )
        (princ "          )\n" OUTFILE)
        (princ "         )\n" OUTFILE)
       )
       (princ "         (entmake (list (cons 0 \"ENDBLK\")))\n" OUTFILE)
       (princ "        )\n" OUTFILE)
       (princ "       )\n" OUTFILE)
      )
     )
     (setq C (+ C 1))
    )
    (foreach NODE BLOCKNESTLIST
     (progn
      (princ (strcat "       ((= (strcase BLKNAME) (strcase \"" NODE "\"))\n") OUTFILE)
      (princ "        (progn\n" OUTFILE)
      (princ "         (entmake)\n" OUTFILE)
      (princ "         (entmake\n" OUTFILE)
      (princ "          (list\n" OUTFILE)
      (setq ENTLIST (tblsearch "BLOCK" NODE))
      (setq ENT (cdr (assoc -2 ENTLIST)))
      (while (/= nil ENTLIST)
       (setq NODE (car ENTLIST))
       (setq ENTLIST (cdr ENTLIST))
       (setq CODE (car NODE))
       (if (and (>= CODE 0) (<= CODE 100) (/= CODE 5))
        (if (= (vl-list-length NODE) nil)
         (progn
          (princ
           (strcat "           (cons "
                   (itoa CODE)
                   " "
                   (if (numberp (cdr NODE))
                    (rtos (cdr NODE) 2 8)
                    (strcat "\"" (cdr NODE) "\"")
                   )
                   ")\n"
           )
           OUTFILE
          )
         )
         (progn
          (princ "           (list" OUTFILE)
          (foreach VAL NODE (princ " " OUTFILE)
                            (if (numberp VAL)
                                (princ (rtos VAL 2 8) OUTFILE)
                                (princ (strcat "\"" VAL "\"") OUTFILE)
                            )
          )
          (princ ")\n" OUTFILE)
         )
        )
       )
      )
      (princ "          )\n" OUTFILE)
      (princ "         )\n" OUTFILE)
      (while (/= ENT nil)
       (setq ENTLIST (entget ENT))
       (if (= "INSERT" (cdr (assoc 0 ENTLIST)))
        (if (= nil (cdr (assoc 2 ENTLIST)))
         (setq BLOCKNESTLIST (append BLOCKNESTLIST (list (cdr (assoc 2 ENTLIST)))))
        )
       )
       (setq ENT (entnext ENT))
       (princ "         (entmake\n" OUTFILE)
       (princ "          (list\n" OUTFILE)
       (while (/= ENTLIST nil)
        (setq NODE (car ENTLIST))
        (setq ENTLIST (cdr ENTLIST))
        (setq CODE (car NODE))
        (if (and (>= CODE 0) (<= CODE 100) (/= CODE 5))
         (if (= (vl-list-length NODE) nil)
          (progn
           (princ
            (strcat "           (cons "
                    (itoa CODE)
                    " "
                    (if (numberp (cdr NODE))
                     (rtos (cdr NODE) 2 8)
                     (strcat "\"" (cdr NODE) "\"")
                    )
                    ")\n"
            )
            OUTFILE
           )
          )
          (progn
           (princ "           (list" OUTFILE)
           (foreach VAL NODE (princ " " OUTFILE)
                             (if (numberp VAL)
                                 (princ (rtos VAL 2 8) OUTFILE)
                                 (princ (strcat "\"" VAL "\"") OUTFILE)
                             )
           )
           (princ ")\n" OUTFILE)
          )
         )
        )
       )
       (princ "          )\n" OUTFILE)
       (princ "         )\n" OUTFILE)
      )
      (princ "         (entmake (list (cons 0 \"ENDBLK\")))\n" OUTFILE)
      (princ "        )\n" OUTFILE)
      (princ "       )\n" OUTFILE)
     )
    )
    (princ "       (T\n" OUTFILE)
    (princ "        (progn\n" OUTFILE)
    (princ "         (alert (strcat \"!!! BLOCK DOES NOT EXIST - \" BLKNAME \" !!!\"))\n" OUTFILE)
    (princ "        )\n" OUTFILE)
    (princ "       )\n" OUTFILE)
    (princ " )\n" OUTFILE)
    (princ ")\n" OUTFILE)
    (close OUTFILE)
   )
  )
  (princ "\n*** Entity not a block ***")
 )
 (setvar "CMDECHO" CMDECHO)
 (setvar "DIMZIN" DIMZIN)
)

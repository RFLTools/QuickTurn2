;
;
;     Program written by Robert Livingston, 2015-11-13
;
;     QT:DRAWENVELOPE draws the vehicle envelope
;
;
(defun QT:DRAWENVELOPE (COLOR VLIST / ALIST ANG1 ANG2 C C2 C3 ENTLISTNEW ENVLIST
                                      FOUND NODE P P1 P2 PA PB PC PD PLIST TMP)

 (setq ENTLISTNEW (list (list (cons 0 "BLOCK")
                              (cons 2 "*U")
                              (cons 8 "0")
                              (cons 70 1)
                              (list 10 0.0 0.0 0.0)
                        )
                  )
 )
 (setq FOUND nil)
 (setq C 0)
 (while (< C (length VLIST))
  (if (setq ENVLIST (if (= (cadr (nth C VLIST)) "LOAD") (cadddr (nth C VLIST)) (caddr (nth C VLIST))))
   (progn
    (setq FOUND T)
    (setq C2 0
          PLIST (cadr (nth C QT:PATHLIST))
          ALIST (caddr (nth C QT:PATHLIST))
    )
    (while (< C2 (1- (length PLIST)))
     (setq P1 (nth C2 PLIST)
           ANG1 (nth C2 ALIST)
           P2 (nth (1+ C2) PLIST)
           ANG2 (nth (1+ C2) ALIST)
           C3 0
     )
     (while (< C3 (length ENVLIST))
      (setq P (nth C3 ENVLIST))
      (setq PA (list (+ (nth 0 P1) (* (nth 0 P) (cos ANG1)) (* -1.0 (nth 1 P) (sin ANG1)))
                     (+ (nth 1 P1) (* (nth 0 P) (sin ANG1)) (* (nth 1 P) (cos ANG1)))))
      (setq PC (list (+ (nth 0 P2) (* (nth 0 P) (cos ANG2)) (* -1.0 (nth 1 P) (sin ANG2)))
                     (+ (nth 1 P2) (* (nth 0 P) (sin ANG2)) (* (nth 1 P) (cos ANG2)))))
      (if (= C3 (- (length ENVLIST) 1))
       (setq P (nth 0 ENVLIST))
       (setq P (nth (+ C3 1) ENVLIST))
      )
      (setq PB (list (+ (nth 0 P1) (* (nth 0 P) (cos ANG1)) (* -1.0 (nth 1 P) (sin ANG1)))
                     (+ (nth 1 P1) (* (nth 0 P) (sin ANG1)) (* (nth 1 P) (cos ANG1)))))
      (setq PD (list (+ (nth 0 P2) (* (nth 0 P) (cos ANG2)) (* -1.0 (nth 1 P) (sin ANG2)))
                     (+ (nth 1 P2) (* (nth 0 P) (sin ANG2)) (* (nth 1 P) (cos ANG2)))))
      (setq ENTLISTNEW (append ENTLISTNEW
                              (list (list (cons 0 "SOLID")
                                          (cons 8 "0")
                                          (list 10 (car PA) (cadr PA) 0.0)
                                          (list 11 (car PB) (cadr PB) 0.0)
                                          (list 12 (car PC) (cadr PC) 0.0)
                                          (list 13 (car PD) (cadr PD) 0.0)
                                          (cons 62 COLOR)
                                    )
                              )
                       )
      )
      (setq C3 (1+ C3))
     )
     (setq C2 (1+ C2))
    )
    (setq C (1+ C))
   )
  )
 )
 (setq ENTLISTNEW (append ENTLISTNEW (list (list (cons 0 "ENDBLK")
                                                 (cons 100 "AcDbBlockEnd")
                                                 (cons 8 "0")
                                           )
                                     )
                  )
 )
 (if FOUND
  (progn
   (entmake)
   (foreach NODE ENTLISTNEW
    (setq TMP (entmake NODE))
   )
   (entmake (list (cons 0 "INSERT")
                  (cons 2 TMP)
                  (list 10 0.0 0.0 0.0)
                  (cons 41 1.0)
                  (cons 42 1.0)
                  (cons 43 1.0)
                  (cons 50 0.0)
            )
   )
   (command "._DRAWORDER" (entlast) "" "BACK")
   (entlast)
  )
  nil
 )
)
